package TaskFlowData {
  item def Task { attribute id: Integer; attribute title: String; attribute description: String; attribute priority: String; attribute status: String; attribute dueDate: String; attribute recurrenceRule: String; attribute parentId: Integer; }
}
